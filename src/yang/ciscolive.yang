module ciscolive {
    namespace "http://ciscolive.network/ciscolive";
    prefix ciscolive;
    yang-version 1.1;

    import ietf-inet-types {
        prefix inet;
    }
    import tailf-common {
        prefix tailf;
    }
    import tailf-ncs {
        prefix ncs;
    }
    import tailf-ned-cisco-ucs {
        prefix ucs;
    }
    import tailf-ned-cisco-nx {
        prefix nx;
    }
    import tailf-ned-vmware-vsphere-portgroup-cfg {
        prefix vmw;
    }

    description
      "Data model for the CiscoLive data center network.";

    revision 2021-11-25 {
        description
          "Initial revision.";
    }

    typedef segment-category {
        tailf:info "Usage category of a given segment.";
        type enumeration {
            enum vm {
                tailf:info "Segment is used for virtual machines.";
            }
            enum netapp {
                tailf:info "Segment is used for NetApp-only traffic.";
            }
            enum fabric-interconnect {
                tailf:info "Segment is used for FI-only traffic.";
            }
            enum peer {
                tailf:info "Segment is used for route peering.";
            }
        }
    }

    grouping route-common {
        leaf redistribute {
            tailf:info "Redistribute this route into OSPF.";
            tailf:cli-boolean-no;
            type boolean;
            default "false";
        }
        leaf data-center {
            tailf:info "Data Center to which this route applies (default is both).";
            type leafref {
                path "/ciscolive/data-center/id";
            }
        }
    }

    grouping description-details {
        choice single-description-or-list {
            case single-description {
                leaf description {
                    tailf:info "Interface description for this interface on all switches.";
                    tailf:cli-suppress-quotes;
                    type string;
                }
            }
            case description-list {
                leaf-list description-list {
                    tailf:info "Interface description per switch (DC1/SW1, DC1/SW2, ...).";
                    ordered-by user;
                    type string;
                    min-elements 2;
                    max-elements 4;
                }
            }
        }
    }

    grouping interface-details {
        uses description-details;
        leaf mode {
            tailf:info "Type of interface.  The 'edge' and 'monitor' modes are considered an error for port-channels.";
            type enumeration {
                enum access {
                    tailf:info "This interface is an access port in a given VLAN.";
                }
                enum trunk {
                    tailf:info "This interface is a trunk port.";
                }
                enum edge {
                    tailf:info "This is a routed interface connected to the network edge.";
                }
                enum cross-dc-link {
                    tailf:info "This link connects DCs.";
                }
                enum monitor {
                    tailf:info "This interface is a SPAN destination port.";
                }
            }
        }
        leaf-list category {
            tailf:info "Usage category of this interface.";
            type segment-category;
            when '../mode = "trunk"';
            min-elements 1;
        }
        leaf vlan {
            tailf:info "Access VLAN for this interface.";
            type leafref {
                path "/ciscolive/vlan/id";
            }
            when '../mode = "access"';
            mandatory true;
        }
        leaf-list allowed-vlan {
            tailf:info "List of allowed VLANs for this trunk.  If this is omitted, VLAN list will be built based on category.";
            tailf:cli-range-list-syntax;
            type leafref {
                path "/ciscolive/vlan/id";
            }
            when '../mode = "trunk"';
        }
    /*leaf access-group {
     *     tailf:info "IPv4 access-list name to apply inbound on this interface.";
     *     type leafref {
     *         path "deref(../../../device)/../ncs:config/nx:ip/nx:access-list/nx:list-name/nx:id";
     *     }
     *     when '../mode = "edge"';
     * }
     * leaf traffic-filter {
     *     tailf:info "IPv6 access-list name to apply inbound on this interface.";
     *     type leafref {
     *         path "deref(../../../device)/../ncs:config/nx:ipv6/nx:access-list/nx:list-name/nx:id";
     *     }
     *     when '../mode = "edge"';
     }*/
    }

    list ciscolive {
        tailf:info "An instance of the CiscoLive network for a given year and location.";
        uses ncs:service-data;
        ncs:servicepoint "ciscolive-servicepoint";
        key "location year";
        leaf location {
            tailf:info "Geographic location (e.g., city) of this instance of the CiscoLive network.";
            type string;
        }
        leaf year {
            tailf:info "Year for this instance of the CiscoLive DC network.";
            type uint16;
        }
        leaf contact {
            tailf:info "Point of contact for the NOC.";
            type string;
            mandatory true;
        }
        leaf bandwidth {
            tailf:info "Max interface bandwidth across all DCs.";
            type uint64 {
                range "1..400000000";
            }
            units "kbps";
            default "100000000";
        }
        leaf tool-server {
            tailf:info "Instance of The Tool serving this CiscoLive.";
            type leafref {
                path "/ciscolive:tool-server/name";
            }
            mandatory true;
        }
        leaf netbox-server {
            tailf:info "Instance of ciscolive-netbox-server serving this CiscoLive.";
            type leafref {
                path "/ciscolive:netbox-server/name";
            }
            mandatory true;
        }
        container management {
            tailf:info "Global management-related configuration.";
            tailf:cli-add-mode;
            container interface {
                tailf:info "Management interface details.";
                tailf:cli-add-mode;
                leaf v4-subnet {
                    tailf:info "IPv4 subnet for the management interface.";
                    type inet:ipv4-prefix;
                    mandatory true;
                }
                leaf v6-prefix {
                    tailf:info "IPv6 prefix for the management interface.";
                    type inet:ipv6-prefix;
                    mandatory true;
                }
                leaf name {
                    tailf:info "Name of the management interface.";
                    type string;
                    default "loopback0";
                    config false;
                }
            }
            leaf-list v4-network {
                tailf:info "List of IPv4 networks used for management.";
                tailf:cli-flat-list-syntax;
                type inet:ipv4-prefix;
                min-elements 1;
            }
            leaf-list v6-network {
                tailf:info "List of IPv6 networks used for management.";
                tailf:cli-flat-list-syntax;
                type inet:ipv6-prefix;
                min-elements 1;
            }
        }
        container ip-info {
            tailf:info "Global IP data used to construct addresses.";
            tailf:cli-add-mode;
            leaf v4-network {
                tailf:info "Major network to use to construct IPv4 addresses.";
                type inet:ipv4-address;
                default "10.0.0.0";
            }
            leaf vlan-octet-position {
                tailf:info "Octet into which the VLAN ID will go (-1 for no VLAN).";
                type union {
                    type enumeration {
                        enum -1;
                    }
                    type uint8 {
                        range "2..3";
                    }
                }
                default "2";
            }
            leaf dc-octet-position {
                tailf:info "Octet into which the data center ID will go (-1 for no DC ID).";
                type union {
                    type enumeration {
                        enum -1;
                    }
                    type uint8 {
                        range "2..3";
                    }
                }
                default "3";
            }
            leaf-list dc-octet {
                tailf:info "Octets for each DC.";
                tailf:cli-flat-list-syntax;
                type uint8;
                ordered-by user;
                // XXX: There is a bug where NSO doesn't process leaf-list defaults.
                default "253";
                default "254";
                max-elements 2;
            }
            leaf cross-dc-octet {
                tailf:info "Octet to use for cross-DC networks.";
                type uint8;
                default "252";
            }
            leaf v6-network {
                tailf:info "Network to use to construct IPv6 addresses.";
                type inet:ipv6-address;
                mandatory true;
            }
        }
        container routing {
            tailf:info "Global static routing configuration.";
            tailf:cli-add-mode;
            list ip {
                tailf:info "IPv4 static route.";
                tailf:cli-suppress-mode;
                key "prefix next-hop";
                leaf prefix {
                    tailf:info "Destination network prefix.";
                    type inet:ipv4-prefix;
                }
                leaf next-hop {
                    tailf:info "Next-hop gateway for prefix.";
                    type inet:ipv4-address;
                }
                uses route-common;
            }
            list ipv6 {
                tailf:info "IPv6 static route.";
                tailf:cli-suppress-mode;
                key "prefix next-hop";
                leaf prefix {
                    tailf:info "Destination network prefix.";
                    type inet:ipv6-prefix;
                }
                leaf next-hop {
                    tailf:info "Next-hop gateway for prefix.";
                    type inet:ipv6-address;
                }
                uses route-common;
            }
            container ospf {
                tailf:info "Global OSPF parameters.";
                tailf:cli-add-mode;
                leaf static-acl-v4 {
                    tailf:info "ACL name for matching IPv4 static routes to redistribute into OSPF.";
                    type string;
                    default "StaticOSPFList";
                    config false;
                }
                leaf static-rm-v4 {
                    tailf:info "Route-map name for matching IPv4 static routes to redistribute into OSPF.";
                    type string;
                    default "StaticOSPF_RM";
                    config false;
                }
                leaf static-acl-v6 {
                    tailf:info "ACL name for matching IPv6 static routes to redistribute into OSPF.";
                    type string;
                    default "StaticOSPFListv6";
                    config false;
                }
                leaf static-rm-v6 {
                    tailf:info "Route-map name for matching IPv6 static routes to redistribute into OSPF.";
                    type string;
                    default "StaticOSPF_RMv6";
                    config false;
                }
                leaf reference-bandwidth {
                    tailf:info "Auto-cost reference (dy default this uses the overall bandwidth).";
                    type uint32 {
                        range "1..4000000";
                    }
                }
            }
            container bgp {
                tailf:info "Global BGP parameters.";
                tailf:cli-add-mode;
                leaf local-as {
                    tailf:info "Local BGP autonomous system number.";
                    type uint32;
                }
                list neighbor {
                    tailf:info "List of BGP peers.";
                    tailf:cli-suppress-mode;
                    key "address";
                    leaf address {
                        tailf:info "IP address of peer router.";
                        type inet:ip-address;
                    }
                    leaf remote-as {
                        tailf:info "Neighbor remote autonomous system.";
                        type uint32;
                        mandatory true;
                    }
                    leaf-list data-center {
                        tailf:info "Data centers that are valid for the peer; default both.";
                        type enumeration {
                            enum 1;
                            enum 2;
                        }
                    }
                    must "../local-as";
                }
                leaf route-map {
                    tailf:info "Route-map for redistributing BGP into OSPF.";
                    type string;
                    default "RedistributeFromBGP";
                    config false;
                }
            }
        }
        container pim {
            tailf:info "Protocol Independent Multicast configuration.";
            tailf:cli-add-mode;
            leaf rp {
                tailf:info "PIM rendez-vous point.";
                type inet:ipv4-address;
            }
            leaf ssm-range {
                tailf:info "SSM range.";
                type inet:ipv4-prefix;
                when '../rp';
                mandatory true;
            }
            leaf group-range-prefix {
                tailf:info "Group range handled by the RP.";
                type inet:ipv4-prefix;
                when '../rp';
                default "224.0.0.0/4";
                config false;
            }
        }
        container dns {
            tailf:info "CiscoLive-wide DNS configuration.";
            tailf:cli-add-mode;
            leaf-list server {
                tailf:info "List of IPv4 DNS servers for general use.";
                tailf:cli-flat-list-syntax;
                ordered-by user;
                type inet:ipv4-address;
                min-elements 2;
            }
            leaf domain {
                tailf:info "DNS domain name.";
                type inet:domain-name;
                mandatory true;
            }
            leaf-list v6-server {
                tailf:info "List of DNS servers to hand out via stateless DHCP.";
                tailf:cli-flat-list-syntax;
                ordered-by user;
                type inet:ipv6-address;
                min-elements 2;
            }
            leaf-list search-list {
                tailf:info "List of DNS domains to search.";
                tailf:cli-flat-list-syntax;
                ordered-by user;
                type inet:domain-name;
            }
        }
        container dhcp {
            tailf:info "CiscoLive-wide DHCP configuration.";
            leaf-list relay {
                tailf:info "List of DHCPv4 relay addresses.";
                tailf:cli-flat-list-syntax;
                ordered-by user;
                type inet:ipv4-address;
                min-elements 2;
            }
        }
        container security {
            tailf:info "Global security parameters for this CiscoLive.";
            tailf:cli-add-mode;
            leaf ospf-key {
                tailf:info "Key to use for MD5 message digest for OSPF.";
                type tailf:aes-cfb-128-encrypted-string;
                mandatory true;
            }
            leaf ospf-key-chain {
                tailf:info "Name of the OSPF keychain to use.";
                type string;
                default "OSPF_KEY";
                config false;
            }
            leaf hsrp-key {
                tailf:info "Key to use for HSRP MD5 message digests.";
                type tailf:aes-cfb-128-encrypted-string;
                mandatory true;
            }
            leaf hsrp-key-chain {
                tailf:info "Name of the HSRP keychain to use.";
                type string;
                default "HSRP_KEY";
                config false;
            }
            list user {
                tailf:info "List of local users.";
                key "name";
                leaf name {
                    tailf:info "Local username.";
                    type string;
                }
                leaf role {
                    tailf:info "NX-OS role for the user.";
                    type enumeration {
                        enum network-admin;
                        enum network-operator;
                    }
                    mandatory true;
                }
                leaf password {
                    tailf:info "Password for the user.";
                    type tailf:aes-cfb-128-encrypted-string;
                    mandatory true;
                }
            }
            container aaa {
                tailf:info "Global AAA server configuration (for TACACS+).";
                tailf:cli-add-mode;
                leaf-list server {
                    tailf:info "AAA servers to use for authentication and authorization.";
                    tailf:cli-flat-list-syntax;
                    ordered-by user;
                    type inet:ipv4-address;
                    min-elements 2;
                }
                leaf tacplus-key {
                    tailf:info "Secret key to use for obfuscating TACACS+.";
                    type tailf:aes-cfb-128-encrypted-string;
                    mandatory true;
                }
                leaf group {
                    tailf:info "AAA group name.";
                    type string;
                    default "AAA";
                    config false;
                }
                leaf deadtime {
                    tailf:info "Amount of time in minutes before considering a server unresponsive.";
                    type uint16 {
                        range "0..1440";
                    }
                    default "10";
                    units "minutes";
                    config false;
                }
                leaf timeout {
                    tailf:info "Timeout in seconds before giving up on a server.";
                    type uint8 {
                        range "1..60";
                    }
                    default "10";
                    units "seconds";
                    config false;
                }
            }
            leaf v4-mgmt-acl {
                tailf:info "Name of the IPv4 VTY access-list for management.";
                type string {
                    length "1..64";
                }
                default "MGMT";
                config false;
            }
            leaf v6-mgmt-acl {
                tailf:info "Name of the IPv6 VTY access-list for management.";
                type string {
                    length "1..64";
                }
                default "MGMT_v6";
                config false;
            }
            leaf v4-attendee-acl {
                tailf:info "Name of the IPv4 access-list for attendee traffic.";
                type string {
                    length "1..64";
                }
                default "IPV4_ACL_COMMON_VLAN";
                config false;
            }
            leaf v6-attendee-acl {
                tailf:info "Name of the IPv6 access-list for attendee traffic.";
                type string {
                    length "1..64";
                }
                default "IPV6_ACL_COMMON_VLAN";
                config false;
            }
        }
        container ntp {
            tailf:info "Global NTP server configuration.";
            leaf-list server {
                tailf:info "NTP servers.";
                tailf:cli-flat-list-syntax;
                ordered-by user;
                type inet:ipv4-address;
                min-elements 2;
            }
        }
        container snmp {
            tailf:info "Global SNMP configuration";
            tailf:cli-add-mode;
            leaf community {
                tailf:info "SNMP community string (read-only)";
                type tailf:aes-cfb-128-encrypted-string;
            }
            leaf user {
                tailf:info "SNMPv3 username.";
                type string;
                mandatory true;
            }
            leaf password {
                tailf:info "SNMPv3 password.";
                type tailf:aes-cfb-128-encrypted-string;
                mandatory true;
            }
        }
        container logging {
            tailf:info "Global logging configuration";
            leaf-list server {
                tailf:info "Syslog servers.";
                tailf:cli-flat-list-syntax;
                ordered-by user;
                type inet:ipv4-address;
                min-elements 1;
            }
        }
        container netflow {
            tailf:info "Global NetFlow configuration";
            leaf exporter {
                tailf:info "IP address of flow exporter server.";
                type inet:ipv4-address;
                mandatory true;
            }
            leaf exporter-port {
                tailf:info "UDP port number on the exporter host.";
                type uint16;
                default "9991";
            }
            leaf interface-timeout {
                tailf:info "How often to send interface statistics.";
                type uint32 {
                    range "0..86400";
                }
                default "60";
                config false;
            }
            leaf template-timeout {
                tailf:info "How often to send data flows.";
                type uint32 {
                    range "1..86400";
                }
                default "60";
                config false;
            }
            leaf v4-monitor {
                tailf:info "NetFlow IPv4 monitor name.";
                type string;
                default "CL-ipv4-nb";
                config false;
            }
            leaf v6-monitor {
                tailf:info "NetFlow IPv6 monitor name.";
                type string;
                default "CL-ipv6-nb";
                config false;
            }
        }
        container monitor {
            tailf:info "SPAN configuration.";
            leaf id {
                tailf:info "Id for the SPAN session (currently only one session supported).";
                type uint8 {
                    range "1..48";
                }
                config false;
                default "1";
            }
            leaf shutdown {
                tailf:info "Whether or not this session is shutdown or active.";
                type boolean;
                default "true";
            }
            leaf direction {
                tailf:info "In which direction to capture the traffic.";
                type enumeration {
                    enum tx;
                    enum rx;
                    enum both;
                }
                default "both";
            }
        }
        list vcenter {
            tailf:info "vCenter for this CiscoLive.";
            key "device";
            leaf device {
                tailf:info "vCenter device name.";
                type leafref {
                    path "/ncs:devices/ncs:device/ncs:name";
                }
                mandatory true;
                must 'contains(deref(.)/../ncs:device-type/ncs:generic/ncs:ned-id, "vmware-vsphere")' {
                    error-message
                      "vCenter devices must use the vmware-vsphere NED";
                    tailf:dependency ".";
                }
            }
            container datacenter {
                tailf:info "The VMware Datacenter object that has a relevant vSwitch.";
                tailf:cli-add-mode;
                leaf name {
                    tailf:info "The VMware Datacenter name that contains the relevant vSwitch.";
                    type leafref {
                        path "deref(../../device)/../ncs:config/vmw:vCenter/vmw:datacenter/vmw:name";
                    }
                    mandatory true;
                }
                leaf cross-dc-vswitch {
                    tailf:info "The VMware vSwitch name for cross-DC VLANs.";
                    type leafref {
                        path "deref(../name)/../vmw:vSwitch/vmw:name";
                    }
                    must 'count(/ciscolive/vcenter[device=current()/../../device]/datacenter[name=current()/../name]/cross-dc-vswitch[. = current()]) <= 1 or
                    count(/ciscolive/vcenter[device=current()/../../device]/datacenter[name=current()/../name]/dc-vswitch[. = current()]) <= 1' {
                        error-message
                          "A vSwitch cannot be a part of more than one CiscoLive.";
                    }
                    mandatory true;
                }
                leaf-list dc-vswitch {
                    tailf:info "The VMware vSwitch name for the DC-specific VLANs.";
                    type leafref {
                        path "deref(../name)/../vmw:vSwitch/vmw:name";
                    }
                    must 'count(/ciscolive/vcenter[device=current()/../../device]/datacenter[name=current()/../name]/cross-dc-vswitch[. = current()]) <= 1 or
                    count(/ciscolive/vcenter[device=current()/../../device]/datacenter[name=current()/../name]/dc-vswitch[. = current()]) <= 1' {
                        error-message
                          "A vSwitch cannot be part of more than one CiscoLive.";
                    }
                    min-elements 2;
                    max-elements 2;
                }
            }
            // In production we must have a vCenter.  However, we need to bootstrap the N9Ks first.
            // min-elements 1;
            max-elements 1;
        }
        list vlan {
            tailf:info "VLANs for use in this instance of CiscoLive.";
            key "id";
            leaf id {
                tailf:info "VLAN ID.";
                type uint16 {
                    range "1..3967";
                }
            }
            leaf name {
                tailf:info "VLAN Name.";
                type string {
                    length "1..128";
                }
                mandatory true;
            }
            leaf category {
                tailf:info "Usage category of VLAN.";
                type segment-category;
                default "vm";
            }
            leaf cross-dc {
                tailf:info "VLAN carried on L2 link between DCs.";
                tailf:cli-boolean-no;
                type boolean;
                default "true";
                when '../category != "peer"';
            }
            leaf routed {
                tailf:info "VLAN should have an SVI.";
                tailf:cli-boolean-no;
                type boolean;
                default "true";
            }
            leaf dhcp {
                tailf:info "VLAN has a DHCP server.";
                tailf:cli-boolean-no;
                type boolean;
                mandatory true;
                when '../routed = "true" and ../category != "peer"';
            }
            leaf native {
                tailf:info "VLAN should be native for UCS.";
                tailf:cli-boolean-no;
                type boolean;
                default "false";
            }
            container ip {
                tailf:info "IPv4-related commands.";
                tailf:cli-add-mode;
                choice prefix-or-dc-or-autogen {
                    case autogen {
                        leaf autogen {
                            tailf:info "IP address is to be determined automatically based on VLAN and DC.";
                            type empty;
                        }
                        when '../category != "peer"';
                    }
                    case prefix {
                        leaf prefix {
                            tailf:info "IPv4 prefix for use when the VLAN is routed and cross-dc.";
                            type inet:ipv4-prefix;
                            mandatory true;
                        }
                        when '../category != "peer" and ../cross-dc = "true"';
                    }
                    case dc {
                        list data-center {
                            tailf:info "Per-data-center IPv4 configuration.";
                            tailf:cli-suppress-mode;
                            key "id";
                            leaf id {
                                tailf:info "Data Center ID.";
                                type leafref {
                                    path "/ciscolive/data-center/id";
                                }
                            }
                            leaf prefix {
                                tailf:info "IPv4 prefix for this DC.";
                                type inet:ipv4-prefix;
                                mandatory true;
                            }
                            min-elements 2;
                            max-elements 2;
                        }
                        when '../category = "peer" or ../cross-dc = "false"';
                    }
                    mandatory true;
                }
                choice attendee-acl-or-name {
                    case name {
                        leaf access-group {
                            tailf:info "IPv4 access-list to apply to the VLAN SVI.";
                            type string {
                                length "1..64";
                            }
                        /*
                        * We don't want a leafref here even if we could since ACLs will be managed by The Tool.
                        */
                        }
                    }
                    case attendee-acl {
                        leaf attendee-access-group {
                            tailf:info "Use standard IPv4 access-list for attendees.";
                            type empty;
                        }
                    }
                }
                when '../routed = "true"';
            }
            container ipv6 {
                tailf:info "IPv6-related commands.";
                tailf:cli-add-mode;
                choice prefix-or-dc-or-autogen {
                    case autogen {
                        leaf autogen {
                            tailf:info "IPv6 address is to be determined automatically based on VLAN and DC.";
                            type empty;
                        }
                        when '../category != "peer"';
                    }
                    case prefix {
                        leaf prefix {
                            tailf:info "IPv6 prefix for use when the VLAN is routed and cross-dc.";
                            type inet:ipv6-prefix;
                        }
                        when '../category != "peer" and ../cross-dc = "true"';
                    }
                    case dc {
                        list data-center {
                            tailf:info "Per-data-center IPv6 configuration.";
                            tailf:cli-suppress-mode;
                            key "id";
                            leaf id {
                                tailf:info "Data Center ID.";
                                type leafref {
                                    path "/ciscolive/data-center/id";
                                }
                            }
                            leaf prefix {
                                tailf:info "IPv6 prefix for this DC.";
                                type inet:ipv6-prefix;
                                mandatory true;
                            }
                            max-elements 2;
                        }
                        when '../category = "peer" or ../cross-dc = "false"';
                    }
                }
                choice attendee-acl-or-name {
                    case name {
                        leaf traffic-filter {
                            tailf:info "IPv6 access-list to apply to the VLAN SVI.";
                            type string {
                                length "1..64";
                            }
                            when '
                            (
                                (../../category != "peer" and ../../cross-dc = "true" and (../prefix != "" or ../autogen)) or
                                ((../../category = "peer" or ../../cross-dc = "false") and count(../data-center) > 0)
                            )';
                        /*
                         * We don't want a leafref here even if we could since ACLs will be managed by The Tool.
                         */
                        }
                    }
                    case attendee-acl {
                        leaf attendee-traffic-filter {
                            tailf:info "Use the standard IPv6 access-list for attendees.";
                            type empty;
                        when '
                            (
                                (../../category != "peer" and ../../cross-dc = "true" and (../prefix != "" or ../autogen))
                            )';
                        }
                    }
                }
                leaf link-local-only {
                    tailf:info "Use link-local addresses only on this SVI.";
                    tailf:cli-boolean-no;
                    type boolean;
                    default "true";
                    when '
                    (
                        (../../category != "peer" and ../../cross-dc = "true" and ../prefix = "" and not(../autogen)) or
                        ((../../category = "peer" or ../../cross-dc = "false") and count(../data-center) = 0)
                    )';
                }
                when '../routed = "true"';
                must '
                (
                    (../cross-dc = "true") or
                    (../category = "peer" and (count(data-center) = 2 or count(data-center) = 0)) or
                    (../cross-dc = "false" and (count(data-center) = 2 or count(data-center) = 0))
                )' {
                    error-message
                      "Invalid number of prefix elements (cross-dc can have at most one, non-cross-dc needs 0 or 2).";
                }
            }
            leaf netbox-id {
                tailf:info "Netbox ID of this VLAN element.";
                type uint64;
            }
            container ospf {
                tailf:info "OSPF sub-commands for this VLAN.";
                tailf:cli-add-mode;
                presence "Enables OSPF on the VLAN SVI.";
                leaf network {
                    tailf:info "Type of OSPF network.";
                    type enumeration {
                        enum broadcast;
                        enum point-to-point;
                    }
                    default "broadcast";
                }
            }
        }
        container vpc-peer {
            tailf:info "vPC peer information such as keepalive link and peer link.";
            tailf:cli-add-mode;
            leaf peer-port-channel {
                tailf:info "Peer port-channel ID.";
                type uint16 {
                    range "1..4096";
                }
                mandatory true;
            }
            leaf-list member-interface {
                tailf:info "Member interface(s) for the vPC peer link.";
                tailf:cli-range-list-syntax;
                type string {
                    pattern
                      '[0-9]+/[0-9]+(/[0-9]+)?';
                }
                min-elements 1;
            }
            leaf keepalive-interface {
                tailf:info "Interface to use for vPC keepalives (either mgmt0 or an Ethernet interface number).";
                type union {
                    type enumeration {
                        enum mgmt0;
                    }
                    type string {
                        pattern
                          '[0-9]+/[0-9]+(/[0-9]+)?';
                    }
                }
                default "mgmt0";
            }
        }
        container interface {
            tailf:info "Physical interface configuration.";
            tailf:cli-add-mode;
            list Ethernet {
                tailf:info "List of ethernet interfaces.";
                tailf:cli-allow-join-with-key;
                key "name";
                leaf name {
                    tailf:info "Ethernet interface name.";
                    type string {
                        pattern
                          '[0-9]+/[0-9]+(/[0-9]+)?';
                    }
                    must "count(/ciscolive/vpc-peer/member-interface[. = current()]) < 1" {
                        error-message
                          "Interface cannot be used as a vPC peer link.";
                    }
                    must "count(../../port-channel/member-interface/name[. = current()]) < 1" {
                        error-message
                          "Interface cannot be used as it is already a port-channel member.";
                    }
                    must "count(/ciscolive/vpc-peer/keepalive-interface[. = current()]) < 1" {
                        error-message
                          "Interface cannot be used as it is already a vPC keepalive interface.";
                    }
                }
                leaf speed {
                    tailf:info "Port speed when this port is less than 10 Gbps.";
                    type enumeration {
                        enum 100 {
                            tailf:info "100 Mbps";
                        }
                        enum 1000 {
                            tailf:info "1 Gbps";
                        }
                    }
                }
                uses interface-details;
                container ip {
                    tailf:info "IPv4 commands for edge interfaces.";
                    choice address-or-dhcp {
                        case address {
                            leaf-list address {
                                tailf:info "IPv4 address for interface on each switch (used with /31).";
                                ordered-by user;
                                type inet:ipv4-address;
                                min-elements 4;
                                max-elements 4;
                            }
                        }
                        case dhcp {
                            leaf dhcp {
                                tailf:info "This interface uses DHCP for edge connectivity.";
                                tailf:cli-boolean-no;
                                type boolean;
                            }
                        }
                        mandatory true;
                    }
                    when '../mode = "edge"';
                }
                container ipv6 {
                    tailf:info "IPv6 related commands for edge interfaces.";
                    leaf-list address {
                        tailf:info "IPv6 address for interface on each switch (used with /127).  Link locals are used if omitted.";
                        ordered-by user;
                        type inet:ipv6-address;
                        max-elements 4;
                        when '../../mode = "edge"';
                        must "count(.) = 0 or count(.) = 4" {
                            error-message
                              "Either no IPv6 addresses should be specified or an address for each switch should be specified.";
                        }
                    }
                }
                leaf mtu {
                    tailf:info "MTU override for this edge interface.";
                    type uint16 {
                        range "1500..9216";
                    }
                    default "9000";
                    when '../mode = "edge"';
                }
                must 'mode = "access" or mode = "edge" or mode = "monitor"' {
                    error-message
                      "Ethernet interfaces can only be access, edge or monitor ports.";
                }
            }
            list port-channel {
                tailf:info "List of port-channel interfaces on this switch.";
                tailf:cli-allow-join-with-key;
                key "name";
                leaf name {
                    tailf:info "Port-channel interface name.";
                    type uint16 {
                        range "1..4096";
                    }
                    must "/ciscolive/vpc-peer/peer-port-channel != current()" {
                        error-message
                          "Port-channel ID is used by the vpc-peer-link.";
                    }
                }
                leaf protocol {
                    tailf:info "Port-channel protocol.";
                    type enumeration {
                        enum lacp;
                        enum none;
                    }
                    default "lacp";
                }
                list member-interface {
                    tailf:info "Member interfaces of this port-channel.";
                    tailf:cli-exit-command "exit-member-interface";
                    key "name";
                    leaf name {
                        type string {
                            pattern
                              '[0-9]+/[0-9]+(/[0-9]+)?';
                        }
                    }
                    uses description-details;
                    min-elements 1;
                }
                uses interface-details;
                must 'mode != "edge" and mode != "monitor"' {
                    error-message
                      "'edge' or 'monitor' are an invalid modes for port-channels.";
                }
            }
        }
        list data-center {
            tailf:info "An instance of a data center site.";
            key "id";
            leaf id {
                tailf:info "Numeric ID of the data center.  There can only be two.";
                type uint8 {
                    range "1..2";
                }
            }
            leaf location {
                tailf:info "Physical location of this data center.";
                type string;
                mandatory true;
            }
            list switch {
                tailf:info "A set of two switches that serve this DC site.";
                key "id";
                leaf id {
                    tailf:info "Numeric ID of the switch.  Switch 1 is the primary and switch 2 is the secondary.";
                    type uint8 {
                        range "1..2";
                    }
                }
                leaf device {
                    tailf:info "Switch name.";
                    type leafref {
                        path "/ncs:devices/ncs:device/ncs:name";
                    }
                    mandatory true;
                    must "count(/ciscolive/data-center/switch/device[. = current()]) = 1" {
                        error-message
                          "Switch can only be part of one DC site in one CiscoLive.";
                    }
                    must 'contains(/ncs:devices/ncs:device[ncs:name=current()]/ncs:device-type/ncs:cli/ncs:ned-id, "cisco-nx")' {
                        error-message
                          "Switches must use the NX-OS CLI NED.";
                    }
                }
                leaf keepalive-ip {
                    tailf:info "IP address of the vPC keepalive IP.";
                    type inet:ipv4-address;
                    mandatory true;
                }
                min-elements 2;
                max-elements 2;
            }
            list fabric-interconnect {
                tailf:info "List of Fabric Interconnects for a given DC site.";
                key "device";
                leaf device {
                    tailf:info "FI device name.";
                    type leafref {
                        path "/ncs:devices/ncs:device/ncs:name";
                    }
                    must 'contains(/ncs:devices/ncs:device[ncs:name=current()]/ncs:device-type/ncs:cli/ncs:ned-id, "cisco-ucs")' {
                        error-message
                          "fabric-interconnects must use a UCS NED.";
                    }
                }
                must "count(/ciscolive/data-center/fabric-interconnect/device[text() = current()]) <= 1" {
                    error-message
                      "A fabric interconnect cannot be a part of more than one DC site.";
                    tailf:dependency ".";
                }
                list vnic-template-trunk {
                    tailf:info "A vNic Template that will act as a fabric trunk, passing all network segments to connected service profiles.";
                    ordered-by user;
                    key "name";
                    leaf name {
                        type string;
                        tailf:info "Unique name of this vNic Template Trunk.";
                    }
                    choice org-or-root {
                        case org {
                            leaf org {
                                type leafref {
                                    path "/ncs:devices/ncs:device[ncs:name=current()/../../device]/ncs:config/ucs:org/ucs:org/ucs:name";
                                }
                                tailf:info "Org name for this vNic Template.";
                            }
                        }
                        case root {
                            leaf root-org {
                                type empty;
                                tailf:info "This vNic Template should be at the root of the org tree.";
                            }
                        }
                        mandatory true;
                    }
                    choice root-or-org-templ {
                        case org-templ {
                            leaf vnic-template {
                                type leafref {
                                    path "/ncs:devices/ncs:device[ncs:name=current()/../../device]/ncs:config/ucs:org/ucs:org[ucs:name=current()/../org]/ucs:vnic-templ/ucs:name";
                                }
                                when '../org != ""';
                                tailf:info "vNic Template name under the parent org.";
                            }
                        }
                        case root-templ {
                            leaf root-vnic-template {
                                type leafref {
                                    path "/ncs:devices/ncs:device[ncs:name=current()/../../device]/ncs:config/ucs:org/ucs:vnic-templ/ucs:name";
                                }
                                when "../root-org";
                                tailf:info "Root-level vNic Template name.";
                            }
                        }
                        mandatory true;
                    }
                    leaf description {
                        type string;
                        tailf:info "Useful information about this vnic-template";
                    }
                    leaf needs-native {
                        tailf:info "This template needs a native VLAN.";
                        tailf:cli-boolean-no;
                        type boolean;
                        default "false";
                    }
                }
            /*
             * The FIs are generally added as a single UCSM (i.e., the cluster).  We only need a minimum of 1 for a DC.
             * While we want to limit the number of UCSM domains in a site, we will not enforce a max here.
             * 
             * Another thing to note is that requiring at least one FI will trigger a chicken/egg problem since this
             * service is used to bootstrap the N9Ks that frontend access to the FIs.
             */
            // min-elements 1;
            }
            min-elements 2;
            max-elements 2;
        }
        action sync-vlans {
            tailf:actionpoint netbox-sync-vlans;
            tailf:info "Sync VLANs from NetBox into this CiscoLive instance.";
            input {
                leaf commit {
                    tailf:info "Whether to commit (merge and delete) changes into NSO.";
                    type boolean;
                    default false;
                }
            }
            output {
                leaf output {
                    type string;
                }
                leaf success {
                    type boolean;
                }
            }
        }
        action sync-acls {
            tailf:actionpoint tool-sync-acls;
            tailf:info "Sync ACL config elements from the Tool into this CiscoLive instance.";
            input {
                leaf commit {
                    tailf:info "Whether to commit (merge) changes into NSO.";
                    type boolean;
                    default false;
                }
            }
            output {
                leaf output {
                    type string;
                }
                leaf success {
                    type boolean;
                }
            }
        }
    }

    list tool-server {
        description "Tool server instance.";
        key name;
        leaf name {
            tailf:info "Friendly name for Tool server.";
            type string;
        }
        choice server-address {
            case dns {
                leaf fqdn {
                    tailf:info "DNS Name for Tool server"; 
                    type inet:domain-name;
                }
            }
            case ip {
                leaf address { 
                    tailf:info "IP address for Tool server";
                    type inet:ipv4-address;
                }
            }
        }
        leaf url { 
            tailf:info "Crafted URL for Tool server.";
            type string; 
            config false;
            tailf:cdb-oper { 
                tailf:persistent true;
            }
        }
        leaf port { 
            tailf:info "TCP Port Tool server listening on.";
            type uint16;
            default 443;
        }
        leaf protocol { 
            tailf:info "HTTP or HTTPS used to connect to The Tool."; 
            type enumeration { 
                enum http;
                enum https;
            }
            default https;
        }
        leaf username {
            tailf:info "Username to use for The Tool.";
            type string;
        }
        leaf password { 
            tailf:info "Password to use for The Tool.";
            type tailf:aes-cfb-128-encrypted-string;
        }
        leaf login-uri {
            tailf:info "URI path to login to the Tool.";
            type string;
            default "/Administration/Login.aspx";
            config false;
        }
        leaf api-endpoint {
            tailf:info "URI path to the API for fetching config elements.";
            type string;
            default "/n/api/v1/config_element/get/json/for_name/";
            config false;
        }
        action verify-status {
            tailf:actionpoint tool-verify-status;
            tailf:info "Perform a status check that the Tool server is reachable.";
            output {
                leaf output { 
                    type string;
                }
                leaf success { 
                    type boolean;
                }
            }
        }
        uses ncs:service-data;
        ncs:servicepoint ciscolive-tool-server-servicepoint;

    }

    list netbox-server {
        description "NetBox server instance.";
        key name;
        leaf name {
            tailf:info "Friendly name for NetBox server.";
            type string;
        }
        choice server-address {
            case dns {
                leaf fqdn {
                    tailf:info "DNS Name for NetBox server"; 
                    type inet:domain-name;
                }
            }
            case ip {
                leaf address { 
                    tailf:info "IP address for NetBox server";
                    type inet:ipv4-address;
                }
            }
        }
        leaf url { 
            tailf:info "Crafted URL for NetBox server.";
            type string; 
            config false;
            tailf:cdb-oper { 
                tailf:persistent true;
            }
        }
        leaf port { 
            tailf:info "TCP Port NetBox server listening on.";
            type uint16;
            default 443;
        }
        leaf protocol { 
            tailf:info "HTTP or HTTPS used to connect to NetBox."; 
            type enumeration { 
                enum http;
                enum https;
            }
            default https;
        }
        leaf api-token { 
            tailf:info "API Token for interacting with NetBox Server.";
            type tailf:aes-cfb-128-encrypted-string;
        } 
        action verify-status {
            tailf:actionpoint netbox-verify-status;
            tailf:info "Perform a status check that the NetBox server is reachable.";
            output {
                leaf output { 
                    type string;
                }
                leaf success { 
                    type boolean;
                }
            }
        }
        uses ncs:service-data;
        ncs:servicepoint ciscolive-netbox-server-servicepoint;

    }
}
